-- Generic
 Version ::= INTEGER

 AlgorithmIdentifier ::= SEQUENCE {
      algorithm OBJECT IDENTIFIER,
      parameters ANY DEFINED BY algorithm OPTIONAL
 }
 PrivateKeyAlgorithmIdentifier ::= AlgorithmIdentifier

 PrivateKey ::= OCTET STRING

 Attribute ::= SEQUENCE {
     type OBJECT IDENTIFIER,
     value SET SIZE(1 .. MAX) OF ANY
 }
 Attributes ::= SET OF Attribute

 -- Private key
 PrivateKeyInfo ::= SEQUENCE {
    version                   Version,
    privateKeyAlgorithm       PrivateKeyAlgorithmIdentifier,
    privateKey                PrivateKey,
    attributes           [0]  IMPLICIT Attributes OPTIONAL }

 -- Public key
 EncryptedPrivateKeyInfo ::=  SEQUENCE {
     encryptionAlgorithm   AlgorithmIdentifier,
     encryptedData   OCTET STRING }

 curveEd25519 OBJECT IDENTIFIER ::= { 1 3 101 112 }
