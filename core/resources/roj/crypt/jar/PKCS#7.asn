-- 请注意：这不是参考文本，它会在运行时被解析
-- see Asn1Context for parser/encoder details
-- 另外我写的解析器比较简陋：所有的引用必须已定义，就像C语言，你可以用别名语法 ( A ::= B ) 来延迟定义

AttributeTypeAndValue ::= SEQUENCE {
	type OBJECT IDENTIFIER,
	value ANY DEFINED BY type
}
RelativeDistinguishedName ::= SET SIZE (1 .. MAX) OF AttributeTypeAndValue
RDNSequence ::= SEQUENCE OF RelativeDistinguishedName
Name ::= CHOICE { rdnSequence RDNSequence }

AlgorithmIdentifier ::= SEQUENCE {
  algorithm OBJECT IDENTIFIER,
  parameters ANY DEFINED BY algorithm OPTIONAL
}

ContentEncryptionAlgorithmIdentifier ::= AlgorithmIdentifier
DigestAlgorithmIdentifier ::= AlgorithmIdentifier
DigestEncryptionAlgorithmIdentifier ::= AlgorithmIdentifier
SignatureAlgorithmIdentifier ::= AlgorithmIdentifier

CertificateSerialNumber::= INTEGER
IssuerAndSerialNumber ::= SEQUENCE {
  issuer Name,
  serialNumber CertificateSerialNumber
}

Signature ::= BIT STRING

CMSVersion ::= INTEGER { v0(0), v1(1), v2(2), v3(3), v4(4) }
Version ::= INTEGER { v1(0), v2(1), v3(2) }

Attribute ::= SEQUENCE {
  type OBJECT IDENTIFIER,
  value SET SIZE(1 .. MAX) OF ANY
}

Attributes ::= SET OF Attribute
UnauthAttributes ::= SET SIZE(1 .. MAX) OF Attribute
SignedAttributes ::= SET SIZE(1 .. MAX) OF Attribute
UnsignedAttributes ::= SET SIZE(1 .. MAX) OF Attribute

SubjectKeyIdentifier ::= OCTET STRING
SignatureValue ::= OCTET STRING
SignerIdentifier ::= CHOICE {
 	issuerAndSerialNumber IssuerAndSerialNumber,
 	subjectKeyIdentifier [0] IMPLICIT SubjectKeyIdentifier
}

SignerInfo ::= SEQUENCE {
 	version CMSVersion,
 	sid SignerIdentifier,
 	digestAlgorithm DigestAlgorithmIdentifier,
 	signedAttrs [0] IMPLICIT SignedAttributes OPTIONAL,
 	signatureAlgorithm SignatureAlgorithmIdentifier,
 	signature SignatureValue,
 	unsignedAttrs[1] IMPLICIT UnsignedAttributes OPTIONAL
}


Time ::= CHOICE {
    generalTime GeneralizedTime
    -- TODO 理论上还有其他类型
}

Validity ::= SEQUENCE {
    notBefore Time,
    notAfter Time
}

SubjectPublicKeyInfo ::= SEQUENCE {
    algorithm AlgorithmIdentifier,
    subjectPublicKey BIT STRING
}

Extension ::= SEQUENCE {
    extnID OBJECT IDENTIFIER,
    critical [1] IMPLICIT BOOLEAN,
    extnValue OCTET STRING
}

Extensions ::= SEQUENCE OF Extension

TBSCertificate ::= SEQUENCE {
    version [0] EXPLICIT Version,
    serialNumber CertificateSerialNumber,
    signature SignatureAlgorithmIdentifier,
    issuer Name,
    validity Validity,
    subject Name,
    subjectPublicKeyInfo SubjectPublicKeyInfo,
    extensions [3] EXPLICIT Extensions
}

-- 这个名字别动
Certificate ::= SEQUENCE {
    tbsCertificate TBSCertificate,
    signatureAlgorithm SignatureAlgorithmIdentifier,
    signature Signature
}

ExtendedCertificateInfo ::= SEQUENCE {
  version CMSVersion,
  certificate Certificate,
  attributes UnauthAttributes }

ExtendedCertificate ::= SEQUENCE {
  extendedCertificateInfo ExtendedCertificateInfo,
  signatureAlgorithm SignatureAlgorithmIdentifier,
  signature Signature
}

Digest ::= OCTET STRING

-- skip subtree
Certificate_Skip ::= SEQUENCE {}
CertificateList ::= SEQUENCE {}
CertificateRevocationLists ::= SET OF CertificateList

ExtendedCertificateOrCertificate ::= CHOICE {
  certificate Certificate_Skip, -- X.509
  extendedCertificate [0] IMPLICIT ExtendedCertificate
}

ExtendedCertificatesAndCertificates ::= SET OF ExtendedCertificateOrCertificate

KeyEncryptionAlgorithmIdentifier ::= AlgorithmIdentifier

Version ::= INTEGER

ContentType ::= OBJECT IDENTIFIER

ContentInfo ::= SEQUENCE {
  contentType ContentType,
  content [0] EXPLICIT ANY DEFINED BY contentType OPTIONAL
}

Data ::= OCTET STRING

DigestAlgorithmIdentifiers ::= SET OF DigestAlgorithmIdentifier

SignerInfos ::= SET OF SignerInfo

SignedData ::= SEQUENCE {
  version Version,
  digestAlgorithms DigestAlgorithmIdentifiers,
  contentInfo ContentInfo,
  certificates[0] IMPLICIT ExtendedCertificatesAndCertificates OPTIONAL,
  crls [1] IMPLICIT CertificateRevocationLists OPTIONAL,
  signerInfos SignerInfos
}

MessageImprint ::= SEQUENCE {
    digestAlgorithm DigestAlgorithmIdentifier
    digest OCTET_STRING
}

-- 这不是从RFC上面摘抄的了
TimestampToken ::= SEQUENCE {
    version Version,
    policy OID,
    messageImprint MessageImprint,
    serialNumber CertificateSerialNumber,
    genTime GENERALIZED_TIME,
    -- nonce = NUMBER ?
    other SET OF ANY
}

pkcs-7 OBJECT IDENTIFIER ::= { iso(1) member-body(2) US(840) rsadsi(113549) pkcs(1) 7 }

-- 注意：故意首字母大写方便 unmarshalAny 函数
Data OBJECT IDENTIFIER ::= { pkcs-7 1 }
SignedData OBJECT IDENTIFIER ::= { pkcs-7 2 }

-- 这是另外一种方式
ecPublicKey@OID OBJECT IDENTIFIER ::= { iso(1) member-body(2) US(840) 10045 2 1 }
